#usage	"<b>Connect Named Net Segments to Pins of a Single Part</b>"
	"<p>"
	"This ULP connects pins in the schematic to short segments of named nets."
	"<p>"
	"Usage:<p>"
	"<blockquote>"
	"1. Open a schematic.<p>"
	"2. Run this ULP on a part to which you wish to make connections.<p>"
	"3. Short connection segments will be created for all the given pins and nets.<p>"
	"</blockquote>"
	"Note:<p>"
	"<blockquote>"
	"This ULP outputs a '.scr' temporary file in the same directory as the project. "
	"It does NOT automatically delete it.<p>"
	"This ULP was tested on EAGLE standard ver 4.15 for Windows.<p>"
	"</blockquote>"
	"<author>Author: <B>Dave Vanden Bout - devb@xess.com</B></author>"


/////////////////////////////////////////////////////////////////////////////////////////
// THIS PROGRAM IS PROVIDED AS IS AND WITHOUT WARRANTY OF ANY KIND, EXPRESSED OR IMPLIED.
/////////////////////////////////////////////////////////////////////////////////////////


#include "useful-routines.ulp"
#include "xess-useful-routines.ulp"


int DO_REGEX = 0;
int DO_BUS = 1;

int pin_bus_high=0, pin_bus_low=0;
int net_bus_high=0, net_bus_low=0;
string pin_name = "";
string net_name = "";
int net_repeat = 0;
int pin_selection = DO_REGEX;
int net_selection = DO_REGEX;
int v_space = 5;
int h_space = 8;


/////////////////////////////////////////////////////////////////////////////////////////
/////////////////////////////////////////////////////////////////////////////////////////
// Start of the main routine.
/////////////////////////////////////////////////////////////////////////////////////////
/////////////////////////////////////////////////////////////////////////////////////////

if(!schematic)
	report_errors("Start this ULP from a schematic!");

/////////////////////////////////////////////////////////////////////////////////////////
// Get input parameters from the user.
/////////////////////////////////////////////////////////////////////////////////////////
int result = dlgDialog("Connect Part")
{
	dlgHBoxLayout
	{
		dlgGroup("Part Info")
		{
			dlgVBoxLayout
			{
				dlgHBoxLayout
				{
					dlgLabel("Part ID ");
					dlgStringEdit(part_id);	// get the identifier for the part whose pins will be connected
				}
				dlgStretch(1);
				dlgSpacing(v_space);
				dlgHBoxLayout
				{
					dlgLabel("Pin Name ");
					dlgStringEdit(pin_name);	// get the name of the pins that will be connected
				}
				dlgSpacing(v_space);
				dlgGroup("Pin Selection")
				{
					dlgRadioButton("Regex",pin_selection);
					dlgRadioButton("Bus",pin_selection);
					dlgHBoxLayout
					{
						dlgStretch(1);
						dlgLabel("High");
						dlgSpinBox(pin_bus_high,0,1024);
						dlgSpacing(h_space);
						dlgLabel("Low");
						dlgSpinBox(pin_bus_low,0,1024);
						dlgStretch(1);
					}
				}
			}
		}
		dlgGroup("Net Info")
		{
			dlgVBoxLayout
			{
				dlgStretch(1);
				dlgHBoxLayout
				{
					dlgLabel("Net Name ");
					dlgStringEdit(net_name);	// get the name for the nets that will be connected to the part's pins
				}
				dlgSpacing(v_space);
				dlgGroup("Net Selection")
				{
					dlgHBoxLayout
					{
						dlgRadioButton("Regex",net_selection);
						dlgCheckBox("Repeat",net_repeat);
					}
					dlgRadioButton("Bus",net_selection);
					dlgHBoxLayout
					{
						dlgStretch(1);
						dlgLabel("High");
						dlgSpinBox(net_bus_high,0,1024);
						dlgSpacing(h_space);
						dlgLabel("Low");
						dlgSpinBox(net_bus_low,0,1024);
						dlgStretch(1);
					}
				}
			}
		}
	}
	dlgHBoxLayout
	{
		dlgStretch(1);
		dlgPushButton("+OK")    dlgAccept();
		dlgPushButton("Cancel") dlgReject();
		dlgStretch(1);
	}
};

// abort if the cancel button was pressed
if(result == 0)
	exit (0);

/////////////////////////////////////////////////////////////////////////////////////////
// Post-process the input parameters.
/////////////////////////////////////////////////////////////////////////////////////////

part_id = strupr(part_id); // make sure part ID is in upper-case to match part IDs on board
if(part_id == "")
	report_errors("ERROR: missing part identifier\n");

pin_name = strupr(pin_name);
if(pin_name == "")
	report_errors("ERROR: missing pin name\n");

net_name = strupr(net_name);
if(net_name == "")
	report_errors("ERROR: missing net name\n");



/////////////////////////////////////////////////////////////////////////////////////////
// initialize the script with global settings
/////////////////////////////////////////////////////////////////////////////////////////

script_text += "SET SELECT_FACTOR 0;\n";	// so we don't pickup anything by mistake
script_text += "GRID MIL;\n"; // all script commands use mils as the dimensional unit
script_text += "SET WIRE_BEND 2;\n"; // so wires will go from (x0 y0) to (x1 y1) without any bends inserted

/////////////////////////////////////////////////////////////////////////////////////////
// Add connections to the part:
/////////////////////////////////////////////////////////////////////////////////////////

string net[];
int num_nets = 0;
string ppin[];
int num_ppins = 0;
schematic(SCH)
{
	SCH.nets(N)
	{
		if(net_selection == DO_BUS)
		{
			if(strstr(N.name,net_name)==0)
			{
				string index_s = strsub(N.name,strlen(net_name));
				if(all_numeric(index_s))
				{
					int index = strtol(index_s);
					if(net_bus_low<=index && index<=net_bus_high)
						net[num_nets++] = N.name;
				}
			}
		}
		else
		{
			if(regexcmp(net_name,N.name,0))
				net[num_nets++] = N.name;
		}
	}

	int net_index = 0;

	SCH.sheets(SH)
	{
		SH.parts(P)
		{
			if(P.name != part_id)
				continue;

			P.instances(I)
			{
				// go through the pins of each instance of each part on each sheet of a schematic
				I.gate.symbol.pins(pin)
				{
					// P.name = chip identifier (e.g., "U1")
					// pin.contact.name = pin number on chip (e.g., "5" or "B13")
					// pin.x, pin.y = (x,y) location of pin in schematic
					// pin.angle = orientation of pin (0, 90, 180, 270)

					if(net_index >= num_nets)
					{
						if(net_repeat)
							net_index = 0;
						else
							break;
					}

					// skip any pin that doesn't even have a contact for connecting a net
					if(!pin.contact)
						continue;

					// skip any pin that is already connected to a net
					if(pin.net != "")
						continue;

					if(pin_selection == DO_BUS)
					{
						if(strstr(I.gate.name,pin_name)==0)
						{
							string index_s = strsub(I.gate.name,strlen(pin_name));
							if(all_numeric(index_s))
							{
								int index = strtol(index_s);
								if(pin_bus_low<=index && index<=pin_bus_high)
								{
									draw_connection(pin,net[net_index],0);
									ppin[num_ppins++] = I.gate.name;
									net_index++;
								}
							}

						}
					}
					else
					{
						if(regexcmp(pin_name,I.gate.name,0))
						{
							draw_connection(pin,net[net_index],0);
							ppin[num_ppins++] = I.gate.name;
							net_index++;
						}
					}
				}
			}
		}
	}
}
finish_up();

if(num_ppins < num_nets && !net_repeat)
{
	sprintf(tmp, "ERROR: %d nets to be connected but there are only %d pins!\n",num_nets,num_ppins);  
	error_text += "Nets:\n";
	for(int i=0; i<num_nets; i++)
		error_text += net[i] + "\n";
	error_text += "Pins:\n";
	for(i=0; i<num_ppins; i++)
		error_text += ppin[i] + "\n";
	num_errors++;
	report_errors("");
}

/////////////////////////////////////////////////////////////////////////////////////////
// Finalize the script.
/////////////////////////////////////////////////////////////////////////////////////////

script_text += "GRID LAST;\n";			// restore grid
script_text += "SET SELECT_FACTOR 0.02;\n";	// restore default select factor

/////////////////////////////////////////////////////////////////////////////////////////
// Execute the script if no errors were found.
/////////////////////////////////////////////////////////////////////////////////////////

finish_up();
