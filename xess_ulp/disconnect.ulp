#usage "<b>Remove Named Net Segments from Pins</b>\n"
       "<p>"
       "This ULP disconnects pins in the schematic from short segments of named nets."
       "<p>"
       "Usage:<p>"
       "<blockquote>1. Open a schematic.<p>"
       "2. Run this ULP with the netscript file containing the net name and pin connections.<p>"
       "3. Short connection segments will be removed for all the given pins and nets.<p></blockquote>"
       "Note:<p>"
       "<blockquote>-This ULP outputs the '.scr' temporary file in the same directory as this ULP. It does NOT automatically delete it.<p>"
       "-This ULP is tested on EAGLE standard ver 4.11 for Windows.<p></blockquote>"
       "<p>"
       "<author>Author: <B>Dave Vanden Bout - devb@xess.com</B></author>"

// THIS PROGRAM IS PROVIDED AS IS AND WITHOUT WARRANTY OF ANY KIND, EXPRESSED OR IMPLIED

#include "useful-routines.ulp"

string lines[];
string connections[];

void readNetList(void)
{
	int pin_cnt = 0;
	for(int n=0; lines[n]; n++)
	{
		if(lines[n][0] == '#')
			continue;
		if(strstr(lines[n], "Signal") == 0)
		{
			string net_parts[];
			int signal_cnt = strsplit (net_parts, lines[n], '\'');
			string net_name = net_parts[1];
			if((net_name[0]=='N') && (net_name[1]=='$')) continue; // don't process unnamed nets
			connections[pin_cnt] = net_parts[3] + "." + net_parts[5] + "\t" + net_name;
			pin_cnt++;
			n++;
			while(strstr(lines[n], ";") < 0)
			{
				signal_cnt = strsplit (net_parts, lines[n], '\'');
				connections[pin_cnt] = net_parts[1] + "." + net_parts[3] + "\t" + net_name;
				pin_cnt++;
				n++;
			}
		}
		if(strstr(lines[n], "Change") == 0)
		{
			;
		}
	}
	return;
}


if(!schematic)
{
	dlgMessageBox("Start this ULP from a schematic!", "OK");
	exit (0);
}

string netscript_file;
if(argv[1])
{
	netscript_file = argv[1];
}
else
{
	netscript_file = dlgFileOpen("Select Script File", "*.scr", "*.*");
}
if(netscript_file)
{
	int n_lines = fileread(lines, netscript_file);
	if(n_lines)
	{
		readNetList();
	}
	else
	{
		dlgMessageBox("Unable to open NetScript file!", "OK");
		exit (0);
	}
}

string script_name = get_project_path() + get_ulp_name() + ".scr";
output(script_name); // clear script file

output(script_name,"at")
{
	printf("DISPLAY NONE Nets;\n");
}

schematic(SCH)
{
	output(script_name,"at")
	{
		SCH.sheets(SH) /* for each sheet in schematic */
		{
			printf("EDIT .S%d;\n",SH.number);
			SH.parts(P) /* for each part in a sheet */
			{
				P.instances(I) /* for each instance of a part */
				{
					I.gate.symbol.pins(pin) /* for each pin of a part instance */
					{
						// P.name = chip identifier (e.g., "U1")
						// pin.contact.name = pin number on chip (e.g., "5" or "B13")
						// pin.x, pin.y = (x,y) location of pin in schematic
						// pin.angle = orientation of pin (0, 90, 180, 270)
						if(!pin.contact) continue;
						string net_name = lookup(connections,P.name+"."+pin.contact.name,1);
						if(!net_name) continue;
						real x = u2inch(pin.x);
						real y = u2inch(pin.y);
						real dx, dy, tx, ty;
						int angle = trunc(pin.angle);
						switch(angle)
						{
						case 0:
							dx = -0.05; dy = 0.0; tx = -0.05; ty = -0.035;
							break;
						case 90:
							dx = 0.0; dy = -0.05; tx = -0.035; ty = -0.05;
							break;
						case 180:
							dx = 0.05; dy = 0.0; tx = 0.05; ty = -0.035;
							break;
						case 270:
							dx = 0.0; dy = 0.05; tx = 0.035; ty = 0.05;
							break;
						default:
							break;
						}
						printf("DELETE (%f %f);\n", x+dx, y+dy);
						// printf("DELETE (%f %f);\n", x+dx+tx, y+dy+ty); // delete text label 
					}
				}
			}
		}
	}
}

output(script_name,"at")
{
	printf("DISPLAY ALL -Pins;\n");
}

exit("SCRIPT '" + script_name + "';\n");
