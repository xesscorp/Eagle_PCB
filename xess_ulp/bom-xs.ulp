string Version = "3.00";

#usage " \
<b>Export a Bill Of Materials / Real-Time Pricing / Online Ordering</b> \
<p> \
Generates a project's bill Of materials (BOM). \
<p> \
In addition, BOMs are genrated that can be imported directly into the Digi-Key and Mouser website ordering systems. \
Also, <b>quantity-based component pricing can be fetched directly from the \
Digi-Key website</b> for a quick estimate of circuit cost. \
<p> \
<author>Author: support@cadsoft.de<br> \
Modified by: Dave Vandenbout / XESS Corp. - devb@xess.com</author> \
<p> \
Version: 2.00 \
Modified by: Jorge Ortiz / Jicamarca Radio Observatory. - jorge.ortiz@jro.igp.gob.pe</author> \
<p> \
Version: 3.00 \
Log: Added support for multi-value parts for Digikey\
"


//==================================================================================================
// TODO List:
//   0. Don't make a career out of this.
//   1. Extract pricing info from Mouser.
//   2. Integrate Octopart.
//==================================================================================================


// THIS PROGRAM IS PROVIDED AS IS AND WITHOUT WARRANTY OF ANY KIND, EXPRESSED OR IMPLIED

// We need these strings in the help text.
string DigikeyBomWebPage = "https://ordering.digikey.com/registereduser/BOMWizard.aspx";
string MouserBomWebPage  = "http://www.mouser.com/tools/tools.aspx";

string HelpText = " \
<h1>How to Generate the Bill Of Materials</h1>  \
<h2><a name=\"Build_Quantity\">Build Quantity</a></h2> \
<p>Enter the number of boards to be built in the <b>Build Quantity</b> field. \
<h2><a name=\"List_Types\">List Types</a></h2> \
<p> \
The BOM format is selected by clicking one of the following radio buttons. \
<ul> \
<li> \
<b>Parts:</b> The BOM consists of a list of parts with each part on its own line. \
</li> \
<li> \
<b>Values:</b> The BOM consists of a list of values where all the parts with  \
the same value are grouped together on one line. \
</li> \
<li> \
<b>Manf:</b> This BOM format is similar to Values with the addition of the  \
manufacturer's name and their part number. This format is useful for sending to distributors to get quotes. \
</li> \
<li> \
<b>Manf+Distributors:</b> This BOM format is similar to Manf with the  \
ordering codes for both Digi-Key and Mouser added. \
</li> \
<li> \
<b>Digi-Key Order:</b> This generates a parts list that can be input directly into  \
<a href=\"" + DigikeyBomWebPage + "\">Digi-Key's BOM Manager</a>. \
</li> \
<li> \
<b>Mouser Order:</b> This generates a parts list that can be input directly into  \
<a href=\"http://www.mouser.com/tools/tools.aspx\">Mouser's BOM import tool</a>. \
</li> \
<li> \
<b>Part Kit Labels:</b> This generates a list of labels that can be applied  \
to parts before they are shipped to an assembly house. (This is XESS-specific.) \
</li> \
</ul> \
<h2><a name=\"Output_Formats\">Output Formats</a></h2> \
<p> \
You have the following output formats available when you view or save a BOM: \
<ul> \
<li> \
<b>Text:</b> Straight ASCII text with no formatting. \
</li> \
<li> \
<b>HTML:</b> HTML-encoded text for inclusion in documents. \
</li> \
<li> \
<b>CSV:</b> Comma-separated-values for importing into spreadsheets. \
</li> \
</ul> \
<h2>Actions</h2> \
<p> \
The buttons along the bottom of the dialog box perform the following actions: \
<ul> \
<li> \
<b>View:</b> Opens a window where you can view the BOM in a format determined by the <a href=\"#List_Types\">List Type</a>  \
and <a href=\"#Output_Formats\">Output Format</a> radio buttons. \
</li> \
<li> \
<b>Save...:</b> Opens a dialog where you can specify a file to store the BOM. \
</li> \
<li> \
<b>Prices:</b> Fetches and displays quantity-based component pricing from Digi-Key. \
</li> \
<li> \
<b>Order:</b> Opens the appropriate order-entry page and displays the BOM in the required import format. \
</li> \
<li> \
<b>Edit:</b> Opens a dialog where you can edit information from a database you have loaded. \
</li> \
<li> \
<b>Help:</b> Brings up this help screen. \
</li> \
<li> \
<b>Close:</b> Terminates the BOM tool. \
</li> \
</ul> \
<h2>Common BOM Operations</h2> \
<h3>Preparing the Schematic</h3>  \
You will need to add the following attributes to the parts in your schematic if you want to use the real-time pricing  \
or online ordering features:  \
<ul>  \
<li>  \
<b>MANF:</b> This attribute holds the name of the manufacturer for the part.  \
</li>  \
<li>  \
<b>MANF#:</b> This attribute holds the manufacturer's part number.  \
</li>  \
<li>  \
<b>DIGIKEY#:</b> This attribute holds the Digi-Key part number.  \
</li>  \
<li>  \
<b>DIGIKEY#S:</b> \
This attribute holds multiple Digi-Key part numbers for different values of the same device. \
This works best by adding the attributes for a specific package directly to a library like rcl or a custom one. \
The format is <pre>Value1:Manf1#:Digikey1#[:Manf1Name]|Value2:Manf2#:Digikey2#[:Manf2Name]|...</pre>\
When using this option, you must fill in the DIGIKEY# and MANF# attributes with the string USE_DIGIKEY#S. \
</li>  \
<li>  \
<b>MOUSER#:</b> This attribute holds the Mouser part number.  \
</li>  \
</ul> \
<p> \
The bad news is you have to lookup and enter these attributes for all the parts in your schematic  \
that you want included in the real-time pricing and/or the online ordering.  \
To assist with this chore, use the <b>attrib-copy</b> ULP to copy the attributes from a single part  \
across all identical parts.  \
<p> \
To save effort, you can also add these attributes directly to the parts in the library.  \
This will still work if it's a generic part like a resistor whose resistance value will affect it's part number, or \
for ICs that have multiple package options (for example, SOIC and TSSOP). You will need to use the DIGIKEY#S attribute. \
<p> \
The good news is you don't need to enter all these attributes for every part to use the ordering/pricing features.  \
For example, parts without a Mouser part number simply aren't included in a Mouser order list.  \
<h3>Viewing the BOM</h3> \
<p> \
Click on the <b>Vie<u>w</u></b> button to get a preview of the BOM output.  \
Use the <a href=\"#List_Types\">List Type</a>  \
and <a href=\"#Output_Formats\">Output Format</a> radio buttons to change how the BOM is displayed. \
<h3>Saving the BOM</h3> \
<p> \
Click on the <b><u>S</u>ave</b> button to save the BOM to a file.  \
Use the <a href=\"#List_Types\">List Type</a>  \
and <a href=\"#Output_Formats\">Output Format</a> radio buttons to select the format and type of data to store. \
<h3>Pricing the BOM</h3> \
<p> \
Click on the <b>Price</b> button to get current pricing information from Digi-Key.  \
Pricing will be adjusted based on the quantity you have entered in the <a href=\"#Build_Quantity\">Build Quantity</a> field.  \
(Pricing from Mouser is not currently supported.) \
<h3>Ordering Parts</h3> \
<p> \
To order parts for your design from Digi-Key or Mouser, select either the  \
<b>Digikey Order</b> or <b>Mouser Order</b> radio button in the <b>List Type</b> box and  \
then click on the <b>Order</b> button.  \
This will open the appropriate order-entry web page in your default browser and  \
display a dialog window with your BOM in the correct import format.  \
(You will have to register and login to each site before you can reach the order-entry page.)  \
Select the parts list in the <b>Parts Order</b> window.  \
Then right-click on the selection and pick <b>Copy</b> from the pop-up menu that appears.  \
Go to the order-entry field in your browser and paste the parts list.  \
Then proceed to complete the order on the particular site you've chosen. \
<h3>Database Operations</h3> \
<p> \
You can pull in additional information about the used parts by loading \
a database file with the <b><u>L</u>oad</b> button. \
<p> \
A database file must consist of lines of text, each of which contains \
one record consisting of CSV (<u>C</u>omma <u>S</u>eparated <u>V</u>alues) \
or TSV (<u>T</u>ab <u>S</u>eparated <u>V</u>alues) data. \
The very first line must contain a \"header\", which defines a unique name for \
each column, and the first column of every following line must contain \
a unique (non-empty) key for this record. \
<p> \
An example for a valid database file would be: \
<pre> \
Key              Manufacturer       Order Code Price \
74LS00N          Texas Instruments  123-456    0.20 \
R-EU_0204/5:4k7  Somebody           RES4k7     0.10 \
</pre> \
Note that the columns are separated by a <b>tab</b> character (you may also \
use a semicolon (';') to separate the columns, but then you will have to make sure \
none of the data items contains a semicolon). \
The keys for looking up records in the database are built from the \
parts' values. If a part's device has defined \"value on\" it means that \
the user needs to specify a particular value for this part, as for \
example with a resistor. In such a case the key consists of the device \
name and the user defined value, separated by a colon (':'). If the \
device has \"value off\", only the device name is used as key (if the \
user has edited the value of such a part and insisted on changing \
it, the edited value will be used). \
<h4>Creating a new database</h4> \
<p> \
Click on the <b><u>N</u>ew</b> button to create a new database. \
You will get a dialog in which you can define the names of the column headers \
for your new database. The first column always contains the key for database \
lookups and can't be deleted (you can edit it, though, to give it a different \
name than the default \"Key\"). This first column will not be visible in the \
generated list, so you don't really need to worry about it. \
<h4>Editing the database</h4> \
<p> \
If you have loaded a database you can either double click on a line \
in the list, or select a line and press Enter (or click on the <b>Edit</b> \
button) to bring up a dialog in which you can edit the database entry \
for this part. If the database has been modified you will be asked if \
you want to save it before leaving the program or loading a new database. \
<h1>Authors</h1> \
<p> \
Original Author: <a href=\"mailto:support@cadsoft.de?subject=bom-xs ULP\">support@cadsoft.de</a> \
<p> \
Modified by: Dave Vandenbout / XESS Corp. - <a href=\"mailto:devb@xess.com?subject=bom-xs ULP\">devb@xess.com</a> \
<p> \
Modified by: Jorge Ortiz / Jicamarca Radio Observatory. - <a href=\"mailto:jorge.ortiz@jro.igp.gob.pe?subject=bom-xs ULP\">jorge.ortiz@jro.igp.gob.pe</a> \
";

if (!schematic) {
    dlgMessageBox(usage + "<hr><b>ERROR: No schematic!</b><p>\nThis program can only work in the schematic editor.");
    exit(1);
}

//XXX
/*
TODO: - Query user for missing database entries ("Check" button)
        - Allow user to define which database columns to actually use
        - dto. for the internal data?
        - store and retrieve the setup?
        - what if this is run in a board?
*/

int BuildQty = 1;
int NumParts;
numeric string Lines[];
numeric string PartName[], PartValue[], PartPrefix[], PartDevice[], PartPackage[], PartHeadline[], PartDescription[], 
PartManf[], PartManfNumber[], PartMouserNumber[], PartDigikeyNumber[], PartMouserPrice[], PartDigikeyPrice[];
numeric string PartDigikeyNumbers[]; /* Added for multi-value part define */
int PartValueOn[];
int Selected;

real TotalDigikeyPrice = -1.0;
real UnitDigikeyPrice = -1.0;

enum { ltParts, ltValues, ltManf, ltManfDisti, ltDigikey, ltMouser, ltLabels }; // List Types
enum { ofText, ofHTML, ofCSV }; // Output Formats
int ListType = 0;
int OutputFormat = 0;

int disableHeader = 0;

string DatabaseFile;
string Database[];
char DatabaseSeparator = '\t';
string DatabaseFields[];
int DatabaseModified = 0;

char ValueSeparator = ':';

string StripWhiteSpace(string s)
{
    while (s && isspace(s[0]))
    s = strsub(s, 1);
    while (s && isspace(s[strlen(s) - 1]))
    s = strsub(s, 0, strlen(s) - 1);
    return s;
}

void CollectPartData(void)
{
    NumParts = 0;

    schematic(SCH) {
        SCH.parts(P) {
            if (P.device.package) {
                PartName[NumParts] = P.name;
                PartValue[NumParts] = P.value;
                PartPrefix[NumParts] = P.device.prefix;
                PartDevice[NumParts] = P.device.name;
                PartPackage[NumParts] = P.device.package.name;
                PartHeadline[NumParts] = P.device.headline;
                PartDescription[NumParts] = P.device.description;
                PartValueOn[NumParts] = P.device.value == "On";
                PartManf[NumParts] = P.attribute["MANF"];
                PartManfNumber[NumParts] = P.attribute["MANF#"];
                PartMouserNumber[NumParts] = P.attribute["MOUSER#"];
                PartDigikeyNumber[NumParts] = P.attribute["DIGIKEY#"];
                PartDigikeyNumbers[NumParts] = P.attribute["DIGIKEY#S"]; /* Added for multi-value part define */
                NumParts++;
            }
        }
    }
}

string DatabaseHeader(void)
{
    string s;

    if (Database[0]) {
        string a[];
        int n = strsplit(a, Database[0], DatabaseSeparator);
        int i;
        for (i = 1; i < n; i++) {
            s += "\t" + a[i];
            DatabaseFields[i - 1] = a[i];
        }
        DatabaseFields[i - 1] = "";
    }
    return s;
}

string DatabaseKey(int i)
{
    string key = PartValue[i];
    if (PartValueOn[i])
    key = PartDevice[i] + ValueSeparator + key;
    return key;
}

string DatabaseLookup(string key, int f)
{
    return lookup(Database, key, DatabaseFields[f], DatabaseSeparator);
}

/* Added for multi-value part support */
string GetDigiKeyEntryByValue(string PartNumbersEntries, string Value, string PartManf) {
	string part_number_array[];
	int number_of_parts = strsplit(part_number_array, PartNumbersEntries, '|');
	
	string PartNumberListEntry_Sections[];
	string iPartValue, iPartManfNumber, iPartNumber;
	for (int i=0; i<number_of_parts; i++) {
		int part_entry_total_sections = strsplit(PartNumberListEntry_Sections, part_number_array[i], ':');
		iPartValue      = PartNumberListEntry_Sections[0]; // Case sensitive for value cases like 10m vs 10M
		iPartManfNumber = PartNumberListEntry_Sections[1];
		iPartNumber     = PartNumberListEntry_Sections[2];
		if (iPartValue == Value) {
			if ((part_entry_total_sections > 3) && (PartNumberListEntry_Sections[3])) { // Might not be set
				PartManf = PartNumberListEntry_Sections[3];
			}
			return iPartManfNumber+":"+iPartNumber+":"+PartManf;
		}
	}
	return "";
}

/* Added for multi-value part support */
string GetDigikeyInfo(string PartManf, string PartManfNumber, string PartNumber, string PartValue, string PartNumbersEntries) {
	// PartNumbersEntries format:
	// Value1:ManufacturerPartNumber1:DigikeyPartNumber1|Value2:ManufacturerPartNumber2:DigikeyPartNumber2|...
	// Return Format
	// ManufacturerPartNumber:DigikeyPartNumber:Manufacturer
	if (PartNumber == "USE_DIGIKEY#S") {
		string DigiKeyEntry = GetDigiKeyEntryByValue(PartNumbersEntries, PartValue, PartManf);
		string dikigey_entry_array[];
		int number_of_parts = strsplit(dikigey_entry_array, DigiKeyEntry, ':');
		PartManfNumber   = dikigey_entry_array[0];
		PartNumber       = dikigey_entry_array[1];
		PartManf         = dikigey_entry_array[2];
	}
	return PartManfNumber+":"+PartNumber+":"+PartManf;
}


void GeneratePartList(void)
{
    int NumLines = 0;
	string CurrentDigikeyinfo, CurrentPartManf, CurrentPartManfNumber, CurrentDigikeyPartNumber;
	string dikigey_entry_array[];

    //XXX column sequence?
    Lines[NumLines++] = "Part\tValue\tDevice\tPackage\tManufacturer\tPart#\tDescription" + DatabaseHeader();
    for (int i = 0; i < NumParts; i++) {
	
		CurrentPartManfNumber    = PartManfNumber[i];
		CurrentPartManf          = PartManf[i];
		CurrentDigikeyPartNumber = PartDigikeyNumber[i];
		if (PartManfNumber[i] == "USE_DIGIKEY#S") {
			CurrentDigikeyinfo = GetDigikeyInfo(PartManf[i], PartManfNumber[i], PartDigikeyNumber[i], PartValue[i], PartDigikeyNumbers[i]);
			int number_of_parts = strsplit(dikigey_entry_array, CurrentDigikeyinfo, ':');
			CurrentPartManfNumber    = dikigey_entry_array[0];
			CurrentDigikeyPartNumber = dikigey_entry_array[1];
			CurrentPartManf          = dikigey_entry_array[2];
		}

        Lines[NumLines] = PartName[i] + "\t" + PartValue[i] + "\t" + PartDevice[i] + "\t" + PartPackage[i] + "\t" + CurrentPartManf + "\t" + CurrentPartManfNumber + "\t" + PartHeadline[i];
        if (Database[0]) {
            string key = DatabaseKey(i);
            for (int f = 0; DatabaseFields[f]; f++)
            Lines[NumLines] += "\t" + DatabaseLookup(key, f);
            Lines[NumLines] += "\t" + key; // hidden field!
        }
        NumLines++;
    }
    Lines[NumLines] = "";
}

void GenerateValueList(void)
{
    int NumLines = 0;
    int Index[];

    //XXX column sequence?
    Lines[NumLines++] = "Qty\tValue\tDevice\tParts" + DatabaseHeader();
    sort(NumParts, Index, PartValue, PartDevice, PartName);
    for (int n1 = 0, n2 = 0; ++n2 <= NumParts; ) {
        int i1 = Index[n1];
        if (n2 < NumParts) {
            int i2 = Index[n2];
            //XXX value on/off?
            if (PartValue[i1] == PartValue[i2] && PartDevice[i1] == PartDevice[i2])//XXX  && lname[i1] == lname[i2])
            continue;
        }
        string Quantity;
        sprintf(Quantity, "%d", (n2 - n1) * BuildQty);
        Lines[NumLines] = Quantity + "\t" + PartValue[i1] + "\t" + PartDevice[i1] + "\t";
        for (;;) {
            Lines[NumLines] += PartName[i1];
            if (++n1 < n2) {
                i1 = Index[n1];
                Lines[NumLines] += ", ";
            }
            else
            break;
        }
        if (Database[0]) {
            string key = DatabaseKey(i1);
            for (int f = 0; DatabaseFields[f]; f++)
            Lines[NumLines] += "\t" + DatabaseLookup(key, f);
            Lines[NumLines] += "\t" + key; // hidden field!
        }
        NumLines++;
    }
    Lines[NumLines] = "";
}

void GenerateManfList(void)
{
    int NumLines = 0;
    int Index[];
	string CurrentDigikeyinfo, CurrentPartManf, CurrentPartManfNumber, CurrentDigikeyPartNumber;
	string dikigey_entry_array[];

    //XXX column sequence?
    Lines[NumLines++] = "Qty\tManf#\tManf\tDevice\tValue\tDescription" + DatabaseHeader();
    sort(NumParts, Index, PartPrefix, PartValue, PartDevice, PartManf, PartManfNumber, PartHeadline, PartDigikeyNumber, PartDigikeyNumbers);
    for (int n1 = 0, n2 = 0; ++n2 <= NumParts; ) {
        int i1 = Index[n1];
        if (n2 < NumParts) {
            int i2 = Index[n2];
            //XXX value on/off?
            if (PartValue[i1] == PartValue[i2] && PartDevice[i1] == PartDevice[i2])//XXX  && lname[i1] == lname[i2])
            continue;
        }

		CurrentPartManfNumber    = PartManfNumber[i1];
		CurrentPartManf          = PartManf[i1];
		CurrentDigikeyPartNumber = PartDigikeyNumber[i1];

		if (PartManfNumber[i1] == "USE_DIGIKEY#S") {
			CurrentDigikeyinfo = GetDigikeyInfo(PartManf[i1], PartManfNumber[i1], PartDigikeyNumber[i1], PartValue[i1], PartDigikeyNumbers[i1]);
			int number_of_parts = strsplit(dikigey_entry_array, CurrentDigikeyinfo, ':');
			CurrentPartManfNumber    = dikigey_entry_array[0];
			CurrentDigikeyPartNumber = dikigey_entry_array[1];
			CurrentPartManf          = dikigey_entry_array[2];
		}
		
        string Quantity;
        sprintf(Quantity, "%d", (n2 - n1) * BuildQty);
        Lines[NumLines] = Quantity 
        + "\t" + CurrentPartManfNumber
        + "\t" + CurrentPartManf
        + "\t" + PartDevice[i1]
        + "\t" + PartValue[i1]
        + "\t" + PartHeadline[i1]; 
        n1 = n2;
        i1 = Index[n2-1];
        NumLines++;
    }
    Lines[NumLines] = "";
}

void GenerateManfDistiList(void)
{
    int NumLines = 0;
    int Index[];
    string TotalDigikeyPriceStr;
    string UnitDigikeyPriceStr;
	string CurrentDigikeyinfo, CurrentPartManf, CurrentPartManfNumber, CurrentDigikeyPartNumber;
	string dikigey_entry_array[];

    //XXX column sequence?
    Lines[NumLines++] = "Qty\tDigikey#\tDigikey $\tMouser#\tMouser $\tManf#\tManf\tDevice\tValue\tDescription" + DatabaseHeader();
    sort(NumParts, Index, PartPrefix, PartValue, PartDevice, PartManf, PartManfNumber, PartHeadline);
    for (int n1 = 0, n2 = 0; ++n2 <= NumParts; ) {
        int i1 = Index[n1];
        if (n2 < NumParts) {
            int i2 = Index[n2];
            //XXX value on/off?
            if (PartValue[i1] == PartValue[i2] && PartDevice[i1] == PartDevice[i2])//XXX  && lname[i1] == lname[i2])
            continue;
        }
		
		CurrentPartManfNumber    = PartManfNumber[i1];
		CurrentPartManf          = PartManf[i1];
		CurrentDigikeyPartNumber = PartDigikeyNumber[i1];
		if (PartManfNumber[i1] == "USE_DIGIKEY#S") {
			// Get actual Digikey parts here from PartDigikeyNumbers
			CurrentDigikeyinfo = GetDigikeyInfo(PartManf[i1], PartManfNumber[i1], PartDigikeyNumber[i1], PartValue[i1], PartDigikeyNumbers[i1]);
			int number_of_parts = strsplit(dikigey_entry_array, CurrentDigikeyinfo, ':');
			CurrentPartManfNumber    = dikigey_entry_array[0];
			CurrentDigikeyPartNumber = dikigey_entry_array[1];
			CurrentPartManf          = dikigey_entry_array[2];
		}
		
        string Quantity;
        sprintf(Quantity, "%d", (n2 - n1) * BuildQty);
        Lines[NumLines] = Quantity 
        + "\t" + CurrentDigikeyPartNumber
        + "\t" + PartDigikeyPrice[i1]
        + "\t" + PartMouserNumber[i1]                                                 
        + "\t" + PartMouserPrice[i1]                                                 
        + "\t" + CurrentPartManfNumber
        + "\t" + CurrentPartManf
        + "\t" + PartDevice[i1]
        + "\t" + PartValue[i1]
        + "\t" + PartHeadline[i1];
        n1 = n2;
        i1 = Index[n2-1];
        NumLines++;
    }
    if(TotalDigikeyPrice >= 0.0)
    {
        sprintf(TotalDigikeyPriceStr,"%11.2f",TotalDigikeyPrice);
        sprintf(UnitDigikeyPriceStr,"%11.2f",UnitDigikeyPrice);
        Lines[NumLines++] = "\t" + "***Total Price***" + "\t" + TotalDigikeyPriceStr;
        Lines[NumLines++] = "\t" + "***Unit Price***" + "\t" + UnitDigikeyPriceStr;
    }
    Lines[NumLines] = "";
}

void GenerateMouserOrderList(void)
{
    int NumLines = 0;
    int Index[];

    //XXX column sequence?
    Lines[NumLines++] = "Mouser Order List";
    sort(NumParts, Index, PartPrefix, PartValue, PartDevice, PartMouserNumber);
    for (int n1 = 0, n2 = 0; ++n2 <= NumParts; ) {
        int i1 = Index[n1];
        if (n2 < NumParts) {
            int i2 = Index[n2];
            //XXX value on/off?
            if (PartValue[i1] == PartValue[i2] && PartDevice[i1] == PartDevice[i2])//XXX  && lname[i1] == lname[i2])
            continue;
        }
        if(PartMouserNumber[i1]){
            string Quantity;
            sprintf(Quantity, "%d", (n2 - n1) * BuildQty);
            Lines[NumLines] = PartMouserNumber[i1] + "|" + Quantity;
            NumLines++;
        }
        n1 = n2;
        i1 = Index[n2-1];
    }
    Lines[NumLines] = "";
}

void GenerateDigikeyOrderList(void)
{
    int NumLines = 0;
    int Index[];
	string CurrentDigikeyinfo, CurrentPartManf, CurrentPartManfNumber, CurrentDigikeyPartNumber;
	string dikigey_entry_array[];

    //XXX column sequence?
    Lines[NumLines++] = "Digikey Order List";
    sort(NumParts, Index, PartPrefix, PartValue, PartDevice, PartDigikeyNumber, PartDigikeyNumbers);
    for (int n1 = 0, n2 = 0; ++n2 <= NumParts; )
    {
        int i1 = Index[n1];
        if (n2 < NumParts)
        {
            int i2 = Index[n2];
            //XXX value on/off?
            if (PartValue[i1] == PartValue[i2] && PartDevice[i1] == PartDevice[i2])//XXX  && lname[i1] == lname[i2])
				continue;
        }
		
		CurrentPartManfNumber    = PartManfNumber[i1];
		CurrentPartManf          = PartManf[i1];
		CurrentDigikeyPartNumber = PartDigikeyNumber[i1];

		if (PartManfNumber[i1] == "USE_DIGIKEY#S") { // Get actual Digikey parts here from PartDigikeyNumbers
			CurrentDigikeyinfo = GetDigikeyInfo(PartManf[i1], PartManfNumber[i1], PartDigikeyNumber[i1], PartValue[i1], PartDigikeyNumbers[i1]);
			int number_of_parts = strsplit(dikigey_entry_array, CurrentDigikeyinfo, ':');
			CurrentPartManfNumber    = dikigey_entry_array[0];
			CurrentDigikeyPartNumber = dikigey_entry_array[1];
			CurrentPartManf          = dikigey_entry_array[2];
		}
		
        if(CurrentDigikeyPartNumber)
        {
            string Quantity;
            sprintf(Quantity, "%d", (n2 - n1) * BuildQty);
            Lines[NumLines] = Quantity + "," + CurrentDigikeyPartNumber;
            NumLines++;
        }
        n1 = n2;
        i1 = Index[n2-1];
    }
    Lines[NumLines] = "";
}

void GenerateLabels(void)
{
    numeric string TempLines[];
    int NumLines = 0;
    int Index[];
	string CurrentDigikeyinfo, CurrentPartManf, CurrentPartManfNumber, CurrentDigikeyPartNumber;
	string dikigey_entry_array[];

    //XXX column sequence?
    sort(NumParts, Index, PartPrefix, PartValue, PartName, PartDevice, PartDigikeyNumber, PartDigikeyNumbers);
    for (int n1 = 0, n2 = 0; ++n2 <= NumParts; ) 
    {
        int i1 = Index[n1];
        if (n2 < NumParts)
        {
            int i2 = Index[n2];
            //XXX value on/off?
            if (PartValue[i1] == PartValue[i2] && PartDevice[i1] == PartDevice[i2])
            continue;
        }
		CurrentPartManfNumber    = PartManfNumber[i1];
		CurrentPartManf          = PartManf[i1];
		CurrentDigikeyPartNumber = PartDigikeyNumber[i1];
		if (PartManfNumber[i1] == "USE_DIGIKEY#S") { // Get actual Digikey parts here from PartDigikeyNumbers
			CurrentDigikeyinfo = GetDigikeyInfo(PartManf [i1], PartManfNumber[i1], PartDigikeyNumber[i1], PartValue[i1], PartDigikeyNumbers[i1]);
			int number_of_parts = strsplit(dikigey_entry_array, CurrentDigikeyinfo, ':');
			CurrentPartManfNumber    = dikigey_entry_array[0];
			CurrentDigikeyPartNumber = dikigey_entry_array[1];
			CurrentPartManf          = dikigey_entry_array[2];
		}

		
        if(CurrentPartManfNumber)
        {
            string Quantity;
            sprintf(Quantity, "%d", (n2 - n1) * BuildQty);
            string date = t2string(time(),"MM/dd/yyyy");
            string Desc = "";
            sprintf(Desc,"%s %s %s", PartValue[i1], PartPackage[i1], PartHeadline[i1]);

            TempLines[NumLines] = "";
            for (;;)
            {
                TempLines[NumLines] += PartName[i1];
                if (++n1 < n2)
                {
                    i1 = Index[n1];
                    TempLines[NumLines] += " ";
                }
                else
                break;
            }
            TempLines[NumLines] += " \\\\" + CurrentPartManfNumber + " \\\\" + Desc + " \\\\Qty: " + Quantity + " \\\\Pckg: 0 \\\\XESS Corp. " + date + " |" ;
            NumLines++;
        }
        n1 = n2;
        i1 = Index[n2-1];
    }

    sort(NumLines, Index, TempLines);
    for(int i=0; i<NumLines; i++)
    {
        Lines[i+1] = TempLines[Index[i]];
    }
    Lines[0] = "Part Kit Labels";
    NumLines++;
    Lines[NumLines] = "";
}

void GenerateList(void)
{
    switch (ListType) {
    case ltParts:     GeneratePartList();         break;
    case ltValues:    GenerateValueList();        break;
    case ltManf:      GenerateManfList();         break;
    case ltManfDisti: GenerateManfDistiList();    break;
    case ltMouser:    GenerateMouserOrderList();  break;
    case ltDigikey:   GenerateDigikeyOrderList(); break;
    case ltLabels:    GenerateLabels();           break;
    }
}

string MakeListHeader(void)
{
    string s;
    schematic(SCH) sprintf(s, "Partlist exported from %s at %s", SCH.name, t2string(time()));
    return s;
}

string MakeListText(void)
{
    int l, Width[];
    for (l = 0; Lines[l]; l++) {
        string a[];
        for (int n = strsplit(a, Lines[l], '\t'); n--; )
        Width[n] = max(Width[n], strlen(a[n]));
    }
    string List;
    if(!disableHeader) {
        List = MakeListHeader() + "\n\n";
    }
    int numHeaders;
    for (l = 1; Lines[l]; l++) {
        List += Lines[l] + "\n";
    }
    return List;
}

string MakeListHTML(void)
{
    string List;
    if(!disableHeader) {
        List = "<b>" + MakeListHeader() + "</b>\n<p>\n";
    }
    List += "<table>\n";
    int numHeaders;
    for (int l = 0; Lines[l]; l++) {
        List += "<tr>";
        string a[];
        int n = strsplit(a, Lines[l], '\t');
        if (l == 0)
        numHeaders = n;
        else
        n = numHeaders; // for the hidden key!
        for (int i = 0; i < n; i++) {
            if (l == 0)
            a[i] = "<b>" + a[i] + "</b>";
            List += "<td>" + a[i] + "</td>";
        }
        List += "</tr>\n";
    }
    List += "</table>\n";
    return List;
}

string MakeListCSV(void)
{
    string List;
    if(!disableHeader) {
        List = MakeListHeader();
    }
    int numHeaders;
    for (int l = 0; Lines[l]; l++) {
        string a[];
        int n = strsplit(a, Lines[l], '\t');
        if (l == 0)
        numHeaders = n;
        else
        n = numHeaders; // for the hidden key!
        for (int i = 0; i < n; i++) {
            List += a[i] + ",";
        }
        List += "\n";
    }
    return List;
}

string MakeList(void)
{
    switch (OutputFormat) {
    case ofText: return MakeListText(); break;
    case ofHTML: return MakeListHTML(); break;
    case ofCSV: return MakeListCSV(); break;
    }
    return "";
}

void ViewList(string title)
{
    dlgDialog(title) {
        string s = MakeList();
        if (OutputFormat != ofHTML)
        s = "<pre>" + s + "</pre>";
        dlgHBoxLayout dlgSpacing(400);
        dlgHBoxLayout {
            dlgVBoxLayout dlgSpacing(300);
            dlgTextView(s);
        }
        dlgHBoxLayout {
            dlgStretch(1);
            dlgPushButton("-Close") dlgReject();
        }
    };
}

void SaveList(void)
{
    string FileName;
    schematic(SCH) FileName = filesetext(SCH.name, OutputFormat == ofHTML ? ".htm" : (OutputFormat == ofCSV ? ".csv" : ".bom"));
    FileName = dlgFileSave("Save Bill Of Material", FileName);
    if (FileName) {
        string a[];
        if (!fileglob(a, FileName) || dlgMessageBox("File '" + FileName + "' exists\n\nOverwrite?", "+&Yes", "-&No") == 0) {
            output(FileName, "wt") {
                printf("%s", MakeListHeader()); // Only put header in when list is saved to file.
                printf("%s", MakeList()); // using "%s" to avoid problems if list contains any '%'
            }
        }
    }
}


//===================================================================================================

real Number[];

int ExtractNumbers(string Line)
{
    int NumNumbers = 0;
    string NumberText = "";
    for(int i=0; i<strlen(Line); i++)
    {
        if(isdigit(Line[i]) || (Line[i]=='.') || (Line[i]==','))
        {
            if(Line[i] != ',')
            NumberText += Line[i];
        }
        else if(strlen(NumberText)!=0)
        {
            Number[NumNumbers++] = strtod(NumberText);
            NumberText = "";
        }
    }
    return NumNumbers;
}

string MakeStringUrlSafe(string s)
{
    // This function replaces characters that would screw-up a URL with their
    // hex equivalent. For example, / is replaced with %2F.
    // Unfortunately, this doesn't seem the fix the problem with the URL
    // for a device like the PIC18F14K50-I/SS.
    string dangerous_chars = "/";
    string safe_s = s;
    for(int i=0; i<strlen(dangerous_chars); i++)
    {
        string substrings[];
        int num_substrings = strsplit(substrings, safe_s, dangerous_chars[i]);
        if(num_substrings > 1)
        {
            string dangerous_char_replacement;
            sprintf(dangerous_char_replacement, "'%%%2X'", dangerous_chars[i]);
            safe_s = substrings[0];
            for(int j=1; j<num_substrings; j++)
            {
                safe_s += dangerous_char_replacement + substrings[j];
            }
        }
    }
    return safe_s;
}

string ExtractDigikeyQtyPricing(string HtmlLine, int NeededQty)
{
    real Number[]; // Store quantity pricing info in this array.
    string NumberText = "";
    int n = 0;
    for(int i=0; i<strlen(HtmlLine); i++)
    {
        if(isdigit(HtmlLine[i]) || (HtmlLine[i]=='.') || (HtmlLine[i]==',')) // Look for digits, decimal points, commas.
        {
            if(HtmlLine[i] != ',') // Keep everything but the commas in a number.
                NumberText += HtmlLine[i];
        }
        else if(strlen(NumberText)!=0) // Found a non-numeric character terminating a number.
        {
            Number[n++] = strtod(NumberText); // Convert the number string that was found.
            NumberText = ""; // Clear number string for continued scanning.
        }
    }

    string UnitPrice;
    switch(n)
    {
        case 2: // quantity + extended price format.
            sprintf(UnitPrice, "%11.2f", Number[1]/Number[0]);
            if(NeededQty < Number[0])
                UnitPrice = "";
            break;
        case 3: // quantity + unit price + extended price format.
            sprintf(UnitPrice, "%11.2f", Number[1]);
            if(NeededQty < Number[0])
                UnitPrice = "";
            break;
        default: // unknown format.
            UnitPrice = "";
            break;
    }
    return UnitPrice;
}

int HasSlash(string s)
{
    return strchr(s, '/') != -1; // Returns true if string contains a '/'.
}

string GetDigikeyPartUrl(string Html, string PartNumber)
{
    // Look for the href that points to the page describing the exact part number.
    int pos = strstr(Html, ">" + PartNumber + "<"); // This is the part number in the link text portion of the href.
    if(pos < 0)
        return ""; // No idea what we have here, so abort.
    Html = strsub(Html, 0, pos); // Keep everything up to the page link text.
    
    pos = strrstr(Html, "href=\""); // Look for the part's page link.
    if(pos < 0)
        return ""; // No link, so abort.
    Html = strsub(Html, pos + strlen("href=\"")); // Remove everything preceding the page link.
    
    pos = strstr(Html, "\""); // Look for the quotation mark ending the page link.
    if(pos < 0)
        return ""; // No quotation, so abort.
        
    return "http://www.digikey.com" + strsub(Html, 0, pos); // Return the part page link.
}

string GetDigikeyPrice(string PartNumber, string PartNumbers, string PartManf, string PartManfNumber, string PartValue, int Quantity) {
    if ((PartNumber == "") && (PartNumbers == ""))
		return "";
        
	// Get part number, either from field or by parsing PartNumbers
	string digikey_info = GetDigikeyInfo(PartManf, PartManfNumber, PartNumber, PartValue, PartNumbers);
	string dikigey_entry_array[];
	int number_of_parts = strsplit(dikigey_entry_array, digikey_info, ':');
	PartManfNumber = dikigey_entry_array[0];
	PartNumber     = dikigey_entry_array[1];
    
    string Url;
    if(HasSlash(PartManfNumber) || HasSlash(PartNumber))
        // If the part number has a '/' in it, then the part has to be found using the Digikey search function.
        //Url = "http://www.digikey.com/scripts/DkSearch/dksus.dll?WT.z_header=search_go&lang=en&keywords="+PartNumber;
        Url = "http://www.digikey.com/product-search/en?WT.z_header=search_go&lang=en&keywords="+PartNumber;
    else
        // If the part number doesn't have a slash in it, then we can figure out the Digikey page without a search.
        sprintf(Url, "http://www.digikey.com/product-detail/en/%s/%s",PartManfNumber,PartNumber);
    string Html;    
    while(netget(Html, Url, 40) >= 0) // Get the HTML page from the URL address.
    {
        int StartPos = strstr(Html,"Extended Price"); // Look for the pricing information.
        if(StartPos >= 0)
        {
            Html = strsub(Html, StartPos+strlen("Extended Price"));
            int EndPos = strstr(Html,"</table>");
            if(EndPos < 0)
                return "***Bad HTML***";
            Html = strsub(Html,0,EndPos);
            string Line[];
            int NumLines = strsplit(Line,Html,'\n');
            string UnitPrice = "***Obsolete***";
            for(int i=0; i<NumLines; i++)
            {
                string p = ExtractDigikeyQtyPricing(Line[i], Quantity);
                if(p != "")
                    UnitPrice = p;
            }
            return UnitPrice;    
        }
        else // No pricing info, so might be a list of possible parts from search function. Look for a link to the part page.
            Url = GetDigikeyPartUrl(Html, PartNumber);
    }
    return "***Unknown***";
}

/*
real Number[];

int ExtractNumbers(string Line)
{
    int NumNumbers = 0;
    string NumberText = "";
    for(int i=0; i<strlen(Line); i++)
    {
        if(isdigit(Line[i]) || (Line[i]=='.') || (Line[i]==','))
        {
            if(Line[i] != ',')
            NumberText += Line[i];
        }
        else if(strlen(NumberText)!=0)
        {
            Number[NumNumbers++] = strtod(NumberText);
            NumberText = "";
        }
    }
    return NumNumbers;
}

string GetDigikeyPrice(string PartNumber, string PartNumbers, string PartManf, string PartManfNumber, string PartValue, int Quantity) {
    string Html;
    if ((PartNumber == "") && (PartNumbers == ""))
		return "";
	
	string Other;
	// Get part number, either from field or by parsing PartNumbers
	string digikey_info = GetDigikeyInfo(PartManf, PartManfNumber, PartNumber, PartValue, PartNumbers);
	string dikigey_entry_array[];
	int number_of_parts = strsplit(dikigey_entry_array, digikey_info, ':');
	PartManfNumber = dikigey_entry_array[0];
	PartNumber     = dikigey_entry_array[1];

    string UrlSafePartManfNumber = MakeStringUrlSafe(PartManfNumber);
    string UrlSafePartNumber = MakeStringUrlSafe(PartNumber);
	string part_url;
	sprintf(part_url, "http://www.digikey.com/product-detail/en/%s/%s",UrlSafePartManfNumber,UrlSafePartNumber);
    if(netget(Html,part_url,40) >= 0)
    {
        int StartPos = strstr(Html,"Extended Price");
        if(StartPos < 0)
        return "A???";
        Html = strsub(Html, StartPos+strlen("Extended Price"));
        int EndPos = strstr(Html,"</table>");
        if(EndPos < 0)
        return "B???";
        Html = strsub(Html,0,EndPos);
        string Line[];
        int NumLines = strsplit(Line,Html,'\n');
        string Price = "";
        for(int i=0; i<NumLines; i++)
        {
            int NumNumbers = ExtractNumbers(Line[i]);
            switch(NumNumbers)
            {
            case 2:
                if(Quantity >= Number[0])
                sprintf(Price,"%11.2f",Number[1]/Number[0]);
                else
                {
                    if (Price == "")
                    sprintf(Price,"%11.2f",Number[1]/Number[0]);
                    return Price;
                }
                break;
            case 3:
                if(Quantity >= Number[0])
                sprintf(Price,"%11.2f",Number[1]);
                else
                {
                    if (Price == "")
                    sprintf(Price,"%11.2f",Number[1]);
                    return Price;
                }
                break;
            default:
                break;
            }
        }
        return Price;
    }
    return neterror();
    return "C???";
}
*/

void GetPartPrices(void)
{
    int Index[];

    TotalDigikeyPrice = 0.0;
    sort(NumParts, Index, PartPrefix, PartValue, PartDevice, PartManf, PartManfNumber);
    for (int n1 = 0, n2 = 0; ++n2 <= NumParts; ) {
        int i1 = Index[n1];
        if (n2 < NumParts) {
            int i2 = Index[n2];
            if (PartValue[i1] == PartValue[i2] && PartDevice[i1] == PartDevice[i2])//XXX  && lname[i1] == lname[i2])
			{
				continue;
			}
        }
        int Quantity = (n2 - n1) * BuildQty;
        PartDigikeyPrice[i1] = GetDigikeyPrice(PartDigikeyNumber[i1],PartDigikeyNumbers[i1],PartManf[i1],PartManfNumber[i1],PartValue[i1],Quantity);
        TotalDigikeyPrice += strtod(PartDigikeyPrice[i1]) * Quantity;
        n1 = n2;
        i1 = Index[n2-1];
    }
    UnitDigikeyPrice = TotalDigikeyPrice / BuildQty;
    GenerateManfDistiList();
}

void PlaceOrder(void)
{
    int saveOutputFormat = OutputFormat;
    OutputFormat = ofText;
    disableHeader = 1;
    switch (ListType) {
    case ltMouser:
        system("rundll32 url.dll,FileProtocolHandler " + MouserBomWebPage);
        GenerateMouserOrderList();
        ViewList("Mouser Parts Order");
        break;
    case ltDigikey:
        system("rundll32 url.dll,FileProtocolHandler " + DigikeyBomWebPage);
        GenerateDigikeyOrderList();
        ViewList("Digi-Key Parts Order");
        break;
    default:
        dlgMessageBox("You must select either 'DigiKey Order' or 'Mouser Order' in the List Type box.");
        break;
    }
    disableHeader = 0;
    OutputFormat = saveOutputFormat;
}

//===================================================================================================


int ReadDatabase(string FileName)
{
    string data;
    if (fileread(data, FileName) > 0) {
        strsplit(Database, data, '\n');
        DatabaseSeparator = (strchr(Database[0], '\t') > -1) ? '\t' : ';';
        DatabaseFile = FileName;
        return 1;
    }
    return 0;
}

// --- Create a new database -------------------------------------------------

string Headers[];
int NumHeaders;
int SelectedHeader;

int NewDatabaseHeaderOk(string Name)
{
    for (int i = 0; i < NumHeaders; i++) {
        if (Name == Headers[i]) {
            dlgMessageBox("Name already defined!");
            return 0;
        }
    }
    return 1;
}

void NewDatabaseEdit(string Title, string Name)
{
    int NewName = !Name;
    dlgDialog(Title + " Header") {
        dlgLabel("&Name:");
        dlgStringEdit(Name);
        dlgHBoxLayout {
            dlgStretch(1);
            dlgPushButton("+Ok") {
                Name = StripWhiteSpace(Name);
                if (!NewName) {
                    if (Name == Headers[SelectedHeader] || NewDatabaseHeaderOk(Name)) {
                        Headers[SelectedHeader] = Name;
                        dlgAccept();
                    }
                }
                else if (Name) {
                    if (NewDatabaseHeaderOk(Name)) {
                        SelectedHeader = NumHeaders;
                        Headers[NumHeaders] = Name;
                        Headers[++NumHeaders] = "";
                        dlgAccept();
                    }
                }
                else
                dlgMessageBox("Name can't be empty!");
            }
            dlgPushButton("-Cancel") dlgReject();
        }
    };
}

void NewDatabase(void)
{
    DatabaseFile = "";
    Database[0] = "";
    GenerateList();
    dlgRedisplay();

    Headers[0] = "Key";
    Headers[1] = "";
    NumHeaders = 1;
    SelectedHeader = -1;
    int result = dlgDialog("New Database") {
        dlgHBoxLayout {
            dlgVBoxLayout {
                dlgLabel("&Headers");
                dlgListBox(Headers, SelectedHeader) NewDatabaseEdit("Edit", Headers[SelectedHeader]);
            }
            dlgVBoxLayout {
                dlgPushButton("&Add") NewDatabaseEdit("New", "");
                dlgPushButton("&Del") {
                    if (SelectedHeader > 0) {
                        for (int i = SelectedHeader; i < NumHeaders - 1; i++)
                        Headers[i] = Headers[i + 1];
                        Headers[--NumHeaders] = "";
                        if (SelectedHeader >= NumHeaders)
                        SelectedHeader = NumHeaders - 1;
                    }
                    else
                    dlgMessageBox("Can't delete the \"Key\" header!\n\nUse \"Edit\" to change it.");
                }
                dlgPushButton("&Edit") NewDatabaseEdit("Edit", Headers[SelectedHeader]);
            }
        }
        dlgHBoxLayout {
            dlgStretch(1);
            dlgPushButton("+Ok") {
                if (NumHeaders > 1)
                dlgAccept();
                else
                dlgMessageBox("Please add at least one header!");
            }
            dlgPushButton("-Cancel") dlgReject();
        }
    };
    if (result) {
        string sep;
        for (int i = 0; Headers[i]; i++) {
            Database[0] += sep + Headers[i];
            sep = "\t";
        }
        DatabaseSeparator = '\t';
        DatabaseModified = 1;
        GenerateList();
    }
}

// ---

void LoadDatabase(void)
{
    string FileName = dlgFileOpen("Choose database file", DatabaseFile, "Database files (*.tsv *.csv);;All files (*)");
    if (FileName) {
        if (ReadDatabase(FileName)) {
            GenerateList();
            DatabaseModified = 0;
        }
    }
}

int SaveDatabase(void)
{
    if (!DatabaseFile) {
        string ext = (DatabaseSeparator == '\t') ? ".tsv" : ".csv";
        DatabaseFile = dlgFileSave("Save database file", "", "Database files (*" + ext + ");;All files (*)");
        if (!DatabaseFile)
        return 0;
        if (fileext(DatabaseFile) != ext)
        DatabaseFile += ext;
    }
    fileerror();
    output(DatabaseFile, "wt") {
        for (int i = 0; Database[i]; i++)
        printf("%s\n", Database[i]);
    };
    return !fileerror();
}

void EditDatabaseEntry(string Key, int Entry)
{
    string Header[];
    string Data[];
    int Fields = strsplit(Header, Database[0], DatabaseSeparator);
    strsplit(Data, Database[Entry], DatabaseSeparator);
    if (!Data[0])
    Data[0] = Key;
    int result = dlgDialog("Edit Database") {
        dlgGridLayout {
            for (int f = 0; f < Fields; f++) {
                dlgCell(f, 0) dlgLabel(Header[f]);
                dlgCell(f, 1) if (f) { dlgStringEdit(Data[f]); } else { dlgLabel(Data[f]); }
            }
        }
        dlgHBoxLayout {
            dlgStretch(1);
            dlgPushButton("+Ok") dlgAccept();
            dlgPushButton("-Cancel") dlgReject();
        }
    };
    if (result) {
        for (int f = 0; f < Fields; f++)
        Data[f] = StripWhiteSpace(Data[f]);
        Database[Entry] = strjoin(Data, DatabaseSeparator);
        DatabaseModified = 1;
        GenerateList();
    }
}

void EditDatabase(void)
{
    if (Database[0]) {
        if (Selected) {
            string a[];
            int KeyField = strsplit(a, Lines[0], '\t');
            strsplit(a, Lines[Selected], '\t');
            string key = a[KeyField];
            string data;
            int entry;
            for (entry = 0; Database[entry]; entry++) {
                strsplit(a, Database[entry], DatabaseSeparator);
                if (a[0] == key) {
                    data = Database[entry];
                    break;
                }
            }
            EditDatabaseEntry(key, entry);
        }
        else
        dlgMessageBox("Please select a list entry first!");
    }
    else
    dlgMessageBox("Please load a database file first!");
}

int OkToClose(void)
{
    if (DatabaseModified) {
        switch (dlgMessageBox("Database has been modified\n\nSave?", "+&Yes", "&No", "-Cancel")) {
        case 0: return SaveDatabase();
        case 1: break;
        case 2: return 0;
        }
    }
    return 1;
}

void DisplayHelp(void)
{
    dlgDialog("Bill Of Material - Help") {
        dlgHBoxLayout dlgSpacing(400);
        dlgHBoxLayout {
            dlgVBoxLayout dlgSpacing(300);
            dlgTextView(HelpText);
        }
        dlgHBoxLayout {
            dlgStretch(1);
            dlgPushButton("-Close") dlgReject();
        }
    };
}

CollectPartData();
GenerateList();

dlgDialog("Bill Of Material - v" + Version) {
    dlgListView("", Lines, Selected) EditDatabase();
    dlgHBoxLayout {
        dlgLabel("Database:");
        dlgLabel(DatabaseFile, 1);
        dlgPushButton("&Load") if (OkToClose()) LoadDatabase();
        dlgPushButton("&New")  if (OkToClose()) NewDatabase();
        dlgStretch(1);
    }
    dlgHBoxLayout {
        dlgLabel("Build Quantity:");
        dlgIntEdit(BuildQty,1,100000000);
        dlgStretch(50);
    }
    dlgHBoxLayout {
        dlgGroup("List Type") {
            dlgRadioButton("&Parts", ListType) GeneratePartList();
            dlgRadioButton("&Values", ListType) GenerateValueList();
            dlgRadioButton("&Manf", ListType) GenerateManfList();
            dlgRadioButton("Manf+Distributors", ListType) GenerateManfDistiList();
            dlgRadioButton("Digikey Order", ListType) GenerateDigikeyOrderList();
            dlgRadioButton("Mouser Order", ListType) GenerateMouserOrderList();
            dlgRadioButton("Part Kit Labels", ListType) GenerateLabels();
        }
        dlgGroup("Output Format") {
            dlgRadioButton("&Text", OutputFormat);
            dlgRadioButton("&HTML", OutputFormat);
            dlgRadioButton("&CSV",  OutputFormat);
        }
        dlgStretch(50);
    }
    dlgHBoxLayout {
        dlgPushButton("Vie&w") ViewList("BOM Preview");
        dlgPushButton("&Save...") SaveList();
        dlgPushButton("Prices") GetPartPrices();
        dlgPushButton("Order") PlaceOrder();
        dlgPushButton("+Edit") EditDatabase();
        dlgPushButton("&Help") DisplayHelp();
        dlgPushButton("-Close") if (OkToClose()) dlgAccept();
        dlgStretch(1);
    }
};
